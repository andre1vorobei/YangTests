module zelax-keepalive {
  namespace
    "urn:zelax:keepalive";

  prefix zelax-keepalive;

  organization
    "Zelax";

  contact
    "Почтовый адрес:
       Россия, 124365, Москва, г. Зеленоград, ул. Заводская, дом 1 Б, строение 2
     Телефон: +7 (495) 748-71-87
     E-Mail: tech@zelax.ru";

  description
    "Этот YANG модуль описывает операцию keepalive.";

  revision 2019-04-22 {
    description
      "Начальная редакция";
  }

  revision 2020-11-10 {
    description
      "Поле keepalive-timeout теперь является обязательным.";
  }

  rpc keepalive {
    description
      "Операция нужна для детектирования неработоспособности соединения между
       netconf-клиентом и netconf-сервером. Netconf-клиент может закрыть
       соединение, если netconf-сервер не ответит на эту операцию сообщением
       <ok/>. Переданный параметр keepalive-timeout задаёт промежуток
       времени от последнего полученного сервером netconf-сообщения до закрытия
       соединения.";

    input {
      leaf keepalive-timeout {
        type uint64;
        mandatory true;
        description
          "Устанавливает промежуток времени (в миллисекундах) от последнего
          полученного сервером netconf-сообщения до закрытия соединения.
          Если параметр равен 0, то сервер не будет закрывать соединение.";
      }
    }
  }
}
