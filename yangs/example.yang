module example {
   namespace "urn:ietf:params:xml:ns:yang:ietf-interfaces";
   prefix "ietf";
   container interfaces {
     list interface {
       key name;
       leaf name {
         type string;
       }
       leaf address {
         type string;
       }
     }
   }
}
